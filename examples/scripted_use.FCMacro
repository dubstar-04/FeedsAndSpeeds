# Demonstration script to run an extended version of the Feed and Speed Calculator FreeCAD addon, 
# which can be installed from the "rpm_override" branch at https://github.com/spanner888/FeedsAndSpeeds/tree/rpm_override
#   Original code is https://github.com/dubstar-04/FeedsAndSpeeds

# This scripts demonstrates original Feed and Speed Calculator capability
# and also the added over ride limits set to match your CNC.

# version 1.0

import PathFeedsAndSpeeds

fsAddon = PathFeedsAndSpeeds.FSCalculation()

# Easy set defaults
tool, limits = fsAddon.initDefaults()

# Now Change defaults to suit your needs. See initFsDefaults() for details.
# Some examples:-
tool.toolDia = 4.0
tool.flutes = 1
fsAddon.material = "Aluminium (6061)"
limits.cncRpmMax = 10000

# Optional print of all the inputs
fsAddon.printInputs(tool, limits)

# Original calculator behaviour, no SCRIPTED over rides
rpm, feed, Hp = fsAddon.calculate(tool) 
# print("\t rpm %d, feed %d, Hp  %.2f & Watts  %d" % (rpm, feed, Hp, Hp*745.6999))

# auto override feed, rpm & power, based on cnc limit settings
rpm, feed, Hp = fsAddon.calcWithAutoOverrides(tool, limits)
print(" -- end Feeds and Speeds integration script/macro --")
